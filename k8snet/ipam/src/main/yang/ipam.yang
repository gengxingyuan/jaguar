module ipam {
    yang-version 1;

    namespace "com.sdnlab.ipam";
    prefix ipam;

    import ietf-inet-types {
        prefix inet;
        revision-date "2013-07-15";
    }
    description
      "Common configuration for the IPAM.";

    revision "2018-08-07" {
        description
            "Initial revision.";
    }

    container ipam-config {
    	description "Ip manager information";
        leaf pod_cidr {
            type string{
            	pattern 
                  '(([0-9]|[1-9][0-9]|1[0-9][0-9]|2[0-4][0-9]|25[0-5])\.){3}'
                + '([0-9]|[1-9][0-9]|1[0-9][0-9]|2[0-4][0-9]|25[0-5])/'
                + '([1-9]|1[0-9]|2[0-9]|3[0-1])';
            }
            
        }
    }

    rpc request-node-ip-block{
    	description "Get the distributed ip block according to the node's name";
    	input{
    		leaf node-name {
    			type string;
    		}
    	}
    	output{
    		leaf global-cidr {
    			type string;
    		}
    		leaf node-cidr {
    			type string;
    		}
    	}
    }

}
